module ietf-dhcp {
  namespace "urn:ietf:params:xml:ns:yang:ietf-dhcp";
  prefix "dhcp";

  import ietf-inet-types {
    prefix inet;
  }
  import ietf-yang-types {
    prefix "yang";
  }
  import ietf-interfaces {
    prefix "if";
  }

  organization "IETF dhc (Dynamic Host Configuration Protocol)
                   Working Group";
  contact      "leo.liubing@huawei.com
                   loukunkun@huawei.com
                   chin.chen@ericsson.com";
  description  "The module for implementing DHCP protocol";

  revision "2016-08-25" {
    description   "initial draft revision";
    reference     "rfc6020";
  }

  grouping dhcp-option {
    description "Configuration option";
    leaf dhcp-server-identifier {
      type  inet:ip-address;
      description "DHCP server identifier";
    }
    leaf domain-name {
      type  string;
      description "Name of the domain";
    }
    leaf domain-name-server {
      type  inet:ip-address;
      description "IPv4 address of the domain";
    }
    leaf interface-mtu {
      type  uint32 {
        range "0..65535";
      }
      description "Minimum Transmission Unit (MTU) of the interface";
    }
    leaf netbios-name-server {
      type  inet:ip-address;
      description "NETBIOS name server";
    }

    leaf netbios-node-type {
      type  uint32 {
        range "0..65535";
      }
      description "NETBIOS node type";
    }
    leaf netbios-scope {
      type  string;
      description "NETBIOS scope";
    }
  }
  container dhcp {
    description
      "DHCP configuration";
    container server {
      description
        "DHCP server configuration";
      leaf lease-time {
        type uint32{
          range "180..31536000";
        }
        description
          "Default network address lease time assigned to DHCP clients";
      }
      leaf ping-packet-number{
        type uint8 {
          range "0..10";
        }
        default "0";
        description "Number of ping packets";
      }
      leaf ping-packet-timeout {
        type uint16 {
          range "0..10000";
        }
        default "500";
        description "Timeout of ping packet";
      }
      container option {
        description "Configuration option";
        uses dhcp-option;
      }
      list dhcp-ip-pool {
        key "ip-pool-name";
        description   "Global IP pool configuration";

        leaf ip-pool-name {
          type string {
            length "1..64";
          }
          description "Name of the IP pool";
        }
        leaf interface {
          type leafref {
            path "/if:interfaces/if:interface/if:name";
          }
          description
            "Name of the interface";
        }
        leaf gateway-ip {
          type inet:ipv4-address;
          description "IPv4 address of the gateway";
        }
        leaf gateway-mask {
          type inet:ip-prefix;
          description "Network submask of the gateway";
        }
        leaf lease-time {
          type uint32 {
            range "180..31536000";
          }
          description
            "Default network address lease time assigned to DHCP clients";
        }
        list manual-allocation {
          key "mac-address ip-address";
          description "Mapping from MAC address to IP address";

          leaf mac-address {
            type yang:mac-address;
            description "MAC address of the host";
          }
          leaf ip-address {
            type inet:ip-address;
            description "IPv4 address of the host";
          }
        }
        list section {
          key "section-index";
          description "IPv4 address for the range";
          leaf section-index {
            type uint16 {
              range "0..255";
            }
            description "Index of IPv4 address range";
          }
          leaf section-start-ip {
            type inet:ipv4-address;
            mandatory "true";
            description "Starting IPv4 Address of a section";
          }
          leaf section-end-ip {
            type inet:ipv4-address;
            description "Last IPv4 Address of a section";
          }
        }
        container option {
          description "Configuration option";
          uses dhcp-option;
        }
      }
    }
    container relay {
      description
        "DHCP relay agent configuration";

      list server-group {
        key "server-group-name";
        description
          "DHCP server group configuration that DHCP relays to";
        leaf server-group-name {
          type string;
          description "Name of a DHCP server group";
        }
        leaf interface {
          type leafref {
            path "/if:interfaces/if:interface/if:name";
          }
          description
            "Name of the interface";
        }
        leaf gateway-address {
          type inet:ipv4-address;
          description "IPv4 address of the gateway";
        }
        leaf-list server-address {
          type inet:ipv4-address;
          description
            "IPv4 address of the server";
        }
      }
    }
    container client {
      description "DHCP client configuration";
      list interfaces {
        key "interface";
        description "Interface configuration";

        leaf interface {
          type leafref {
            path "/if:interfaces/if:interface/if:name";
          }
          description "Name of the interface";
        }
        leaf client-id {
          type string;
          description "DHCP client identifier";
        }
        leaf lease {
          type uint32 {
            range "1..4294967295";
          }
          description "Default network address lease time assigned to DHCP clients";
        }
      }
    }
  }
  container dhcp-state {
    config "false";
    description
      "DHCP state data";
    container server {
      description
        "DHCP server state data";
      container packet-statistics {
        description
          "Packet statistics";
        container receive {
          description
            "Number of received packets";

          leaf decline-packet {
            type uint32;
            config "false";
            description "Total number of DHCPDECLINE packets";
          }
          leaf discover-packet {
            type uint32;
            config "false";
            description "Total number of DHCPDISCOVER packets";
          }
          leaf request-packet {
            type uint32;
            config "false";
            description "Total number of DHCPREQUEST packets";
          }
          leaf release-packet {
            type uint32;
            config "false";
            description "Total number of DHCPRELEASE packets";
          }
          leaf inform-packet {
            type uint32;
            config "false";
            description "Total number of DHCPINFORM packets";
          }
        }
        container send {
          description
            "Number of sent packets";

          leaf offer-packet {
            type uint32;
            config "false";
            description "Total number of DHCPOFFER packets";
          }
          leaf ack-packet {
            type uint32;
            config "false";
            description "Total number of DHCPACK packets";
          }
          leaf nack-packet {
            type uint32;
            config "false";
            description "Total number of DHCPNAK packets";
          }
        }
      }
      container host {
        description
          "Host status information";
        leaf interface {
          type string;
          config "false";
          description "Name of the interface";
        }
        leaf host-ip {
          type string;
          config "false";
          description "IPv4 address of the host";
        }
        leaf host-hardware-address {
          type string;
          config "false";
          description "MAC address of the host";
        }
        leaf lease {
          type uint32;
          config "false";
          description "Default network address lease
                       time assigned to DHCP clients";
        }
        leaf type {
          type enumeration {
            enum automatic{
              description
              "DHCP assigns a permanent IP address to a client";
            }
            enum dynamic{
              description
              "DHCP assigns an IP address to a client
                  for a limited period of time";
            }
            enum manual{
              description
              "a client's IP address is assigned by the
               network administrator, and DHCP is used
            simply to convey the assigned address to the client";
            }
          }
          config "false";
          description "Mechanisms for IP address allocation";
        }
      }
      list ip-pool {
        key "ip-pool-name";
        description   "Global IP pool configuration";

        leaf ip-pool-name {
          type string {
            length "1..64";
          }
          description "Name of an IP pool";
        }
        leaf gateway-ip {
          type inet:ip-address;
          description "IPv4 address of the gateway";
        }
        leaf gateway-mask {
          type inet:ip-prefix;
          description "Network submask of the gateway";
        }
        leaf used-ip-count {
          type uint32;
          config "false";
          description "Total number of used IPv4 addresses";
        }
        leaf idle-ip-count  {
          type uint32;
          config "false";
          description "Total number of idle IPv4 addresses";
        }
        leaf conflict-ip-count {
          type uint32;
          config "false";
          description "Total number of conflict IPv4 addresses";
        }
        leaf total-ip-count  {
          type uint32;
          config "false";
          description "Total number of IPv4 addresses";
        }
      }
    }
    container relay {
      description
        "DHCP reply agent state data";

      container packet-statistics {
        description
          "Packet statistics";
        container receive {
          description
            "Number of received packets";

          leaf discover-packet {
            type uint32;
            config "false";
            description "Total number of DHCPDISCOVER packets";
          }
          leaf offer-packet {
            type uint32;
            config "false";
            description "Total number of DHCPOFFER packets";
          }
          leaf request-packet {
            type uint32;
            config "false";
            description "Total number of DHCPREQUEST packets";
          }
          leaf decline-packet {
            type uint32;
            config "false";
            description "Total number of DHCPDECLINE packets";
          }
          leaf ack-packet {
            type uint32;
            config "false";
            description "Total number of DHCPACK packets";
          }
          leaf nack-packet {
            type uint32;
            config "false";
            description "Total number of DHCPNAK packets";
          }
          leaf release-packet {
            type uint32;
            config "false";
            description "Total number of DHCPRELEASE packets";
          }
          leaf inform-packet {
            type uint32;
            config "false";
            description "Total number of DHCPINFORM packets";
          }
        }
        container send {
          description
            "Number of sent packets";

          leaf discover-packet {
            type uint32;
            config "false";
            description "Total number of DHCPDISCOVER packets";
          }
          leaf offer-packet {
            type uint32;
            config "false";
            description "Total number of DHCPOFFER packets";
          }
          leaf request-packet {
            type uint32;
            config "false";
            description "Total number of DHCPREQUEST packets";
          }
          leaf decline-packet {
            type uint32;
            config "false";
            description "Total number of DHCPDECLINE packets";
          }
          leaf ack-packet {
            type uint32;
            config "false";
            description "Total number of DHCPACK packets";
          }
          leaf nack-packet {
            type uint32;
            config "false";
            description "Total number of DHCPNAK packets";
          }
          leaf release-packet {
            type uint32;
            config "false";
            description "Total number of DHCPRELEASE packets";
          }
          leaf inform-packet {
            type uint32;
            config "false";
            description "Total number of DHCPINFORM packets";
          }
        }
      }
    }
    container client {
      description
        "DHCP client state data";

      container packet-statistics {
        description
          "Packet statistics";
        container receive {
          description
            "Number of received packets";
          leaf offer-packet {
            type uint32;
            config "false";
            description "Total number of DHCPOFFER packets";
          }
          leaf ack-packet {
            type uint32;
            config "false";
            description "Total number of DHCPACK packets";
          }
          leaf nack-packet {
            type uint32;
            config "false";
            description "Total number of DHCPNAK packets";
          }
        }
        container send {
          description
            "Number of sent packets";

          leaf decline-packet {
            type uint32;
            config "false";
            description "Total number of DHCPDECLINE packets";
          }
          leaf discover-packet {
            type uint32;
            config "false";
            description "Total number of DHCPDISCOVER packets";
          }
          leaf request-packet {
            type uint32;
            config "false";
            description "Total number of DHCPREQUEST packets";
          }
          leaf release-packet {
            type uint32;
            config "false";
            description "Total number of DHCPRELEASE packets";
          }
          leaf inform-packet {
            type uint32;
            config "false";
            description "Total number of DHCPINFORM packets";
          }
        }
      }
    }
  }
}
