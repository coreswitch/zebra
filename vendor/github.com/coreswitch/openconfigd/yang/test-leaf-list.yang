module test-leaf-list {
  yang-version "1";

  namespace "http://coreswitch.io/";
  prefix "coreswitch";

  import ietf-inet-types {
    prefix inet;
  }

  container top {
    leaf-list segments {
      type inet:ipv6-address;
    }
  }
}
