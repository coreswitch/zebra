module test-mandatory {
  yang-version "1";

  namespace "http://coreswitch.io/";
  prefix "coreswitch";

  import ietf-inet-types {
    prefix inet;
  }

  container top {
    leaf value {
      type string;
    }
    leaf mandatory {
      type string;
      mandatory true;
    }
  }

  container top-presence {
    presence;
    leaf value {
      type string;
    }
    leaf mandatory {
      type string;
      mandatory true;
    }
  }

  container top-key {
    list key {
      key "first";
      leaf first {
        type string;
      }
      leaf mandatory {
        type string;
        mandatory true;
      }
    }
  }

  container static {
    list route {
      key "prefix";
      leaf prefix {
        type inet:ipv4-prefix;
      }
      list nexthop {
        key "address";
        leaf "address" {
          type inet:ipv4-address;
          mandatory true;
        }
      }
    }
  }
}
